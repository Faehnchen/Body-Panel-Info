# # # # # # # # # # # # # # # # # # # # # # # # # # # # # # # # # # # # # # # # # # #
#                                                                                   #
#   ██████                 ██            ███████                              ██    #
#   ░█░░░░██               ░██  ██   ██  ░██░░░░██                            ░██   #
#   ░█   ░██   ██████      ░██ ░░██ ██   ░██   ░██  ██████   ███████   █████  ░██   #
#   ░██████   ██░░░░██  ██████  ░░███    ░███████  ░░░░░░██ ░░██░░░██ ██░░░██ ░██   #
#   ░█░░░░ ██░██   ░██ ██░░░██   ░██     ░██░░░░    ███████  ░██  ░██░███████ ░██   #
#   ░█    ░██░██   ░██░██  ░██   ██      ░██       ██░░░░██  ░██  ░██░██░░░░  ░██   #
#   ░███████ ░░██████ ░░██████  ██       ░██      ░░████████ ███  ░██░░██████ ███   #
#   ░░░░░░░   ░░░░░░   ░░░░░░  ░░        ░░        ░░░░░░░░ ░░░   ░░  ░░░░░░ ░░░    #
#                                                                                   #
#          ██            ████                        ’Body-Panel-Info.FCMacro’      #
#         ░██           ░██░                                                        #
#         ░██ ███████  ██████  ██████                 Faehnchen, 18 Okt. 2026       #
#         ░██░░██░░░██░░░██░  ██░░░░██                                              #
#         ░██ ░██  ░██  ░██  ░██   ░██                FreeCAD version 1.1.4         #
#         ░██ ░██  ░██  ░██  ░██   ░██                                              #
#         ░██ ███  ░██  ░██  ░░██████                 License: MIT (see end)        #
#         ░░ ░░░   ░░   ░░    ░░░░░░                                                #
# # # # # # # # # # # # # # # # # # # # # # # # # # # # # # # # # # # # # # # # # # #

# About:
# ¯¯¯¯¯¯
#   This Macro adds some useful information about the physical properties of the
#   3D volumes in a PartDesign-Body-container to it's ’Data’-panel:

#   · Assigned Material
#   · Material Density
#   · Volume in mm³
#   · Mass in g and lb

#   You can view all these values in one glance inside the panel. Toggle the display
#   of units on and off with a checkbox.

#   Units stay consistent regardless how big the model grows (no unit shifting)

# Usage:
# ¯¯¯¯¯¯
#   Put this script into the macro folder specific to your OS and installation method
#   (investigate location: Edit > Preferences > Python > Macro)

#   Select and activate the PartDesign Body container you want to add the property
#   infos. Run the Macro.

#   Note: The Macro only runs if there is already a volume in the body container!
#
#   After all properties are created, manually set the ones with leading ’_’ to
#   ’Hidden’ (right-click > Status) and the other ones to ’Read Only’.

#   The values most often trail one feature of the model behind. For displaying the
#   definitive values, recompute the whole model or check/uncheck the units-display
#   switch.

# + + + + + + + + + + + + + + + + + + + + + + + + + + + + + + + + + + + + + + + + + +

import FreeCAD
import PartDesign

# Get the name of the active document
active_doc = App.activeDocument()
# Get the name of the active body
active_body = Gui.ActiveDocument.ActiveView.getActiveObject('pdbody')

# Check if a body is activated
def active_test():
    if str(active_body) == 'None':
        print('No active body selected')
        FreeCAD.Console.PrintError('Macro Body-Panel-Info: ' +
        'Activate the Part Design Body you want to run the script on!\n')
        return 1
    else:
        return 0

# Start: + + + + + + + + + + + + + + + + + + + + + + + + + + + + + + + + + + + + + +
# ¯¯¯¯¯¯
if active_test() == 0:

    # Check if a volume exists and notify > abort if shape is null
    def vol_test():
        if str(active_body.Shape.BoundBox.XLength) == "-inf":
            print("Body has no volume.")
            FreeCAD.Console.PrintError('Macro: Body-Panel-Info: Your Body "' +
            active_body.Label + '" has no volume!\n')
            return 1
        else:
            return 0

    # Check if the macro was already applied to the selected body
    def done_test():
        if hasattr(active_body, "_Density"):
            print('Already done!')
            FreeCAD.Console.PrintError('Macro Body-Panel-Info: ' +
            'Already added properties to "' + active_body.Label + '".\n')
            return 1
        else:
            return 0

    if vol_test() == 0 and done_test() == 0:
        print("Macro: Body-Panel-Info: Adding infos...")
        # Highlight the active body
        Gui.Selection.addSelection(active_doc.Name,active_body.Name)

        # Volume value for calculation (hidden)
        active_body.addProperty('App::PropertyFloat', '_Volume', 'Base', '')
        active_body.setExpression('_Volume', u'.Shape.Volume')
        # Density value for calculation (hidden)
        active_body.addProperty('App::PropertyFloat', '_Density', 'Base', '')
        active_body.setExpression('_Density', u'.ShapeMaterial.PropertyObjects[<<Density>>].Value * 1000000')
        # Checkbox for units display
        active_body.addProperty('App::PropertyBool', 'ShowUnits', 'Base', '')
        FreeCAD.getDocument(active_doc.Name).getObject(active_body.Name).ShowUnits = False
        # Assigned Material
        active_body.addProperty('App::PropertyString', 'AssignedMaterial', 'Base', '')
        active_body.setExpression('AssignedMaterial', u'.ShapeMaterial.Name')
        # Density display
        active_body.addProperty('App::PropertyString', 'Density', 'Base', '')
        active_body.setExpression('Density', u'str(_Density) + str(ShowUnits ? << g/cm\xb3>> : <<>>)')
        # Mass in grams
        active_body.addProperty('App::PropertyString', 'MassInGrams', 'Base', '')
        active_body.setExpression('MassInGrams', u'str(round(_Volume * _Density) / 1000) + str(ShowUnits ? << g>> : <<>>)')
        # Mas in pounds
        active_body.addProperty('App::PropertyString', 'MassInPounds', 'Base', '')
        active_body.setExpression('MassInPounds', u'str(round(_Volume * _Density * 0.0022046226) / 1000) + str(ShowUnits ? << lb>> : <<>>)')
        # Volume display
        active_body.addProperty('App::PropertyString', 'Volume', 'Base', '')
        active_body.setExpression('Volume', u'<<%d>> % round(.Shape.Volume) + str(ShowUnits ? << mm\xb3>> : <<>>)')

        print("Macro Body-Panel-Info: Finished.")
else:
    print('Macro Body-Panel-Info: Aborted.')

# # # # # # # # # # # # # # # # # # # # # # # # # # # # # # # # # # # # # # # #
# Copyright (c) 2026 Faehnchen, MIT License                                   #
#                                                                             #
# Permission is hereby granted, free of charge, to any person obtaining a     #
# copy of this software and associated documentation files (the "Software"),  #
# to deal in the Software without restriction, including without limitation   #
# the rights to use, copy, modify, merge, publish, distribute, sublicense,    #
# and/or sell copies of the Software, and to permit persons to whom the Soft- #
# ware is furnished to do so, subject to the following conditions:            #
#                                                                             #
# The above copyright notice and this permission notice shall be included in  #
# all copies or substantial portions of the Software.                         #
#                                                                             #
# THE SOFTWARE IS PROVIDED "AS IS", WITHOUT WARRANTY OF ANY KIND, EXPRESS     #
# OR IMPLIED, INCLUDING BUT NOT LIMITED TO THE WARRANTIES OF MERCHANTABILITY, #
# FITNESS FOR A PARTICULAR PURPOSE AND NONINFRINGEMENT. IN NO EVENT SHALL THE #
# AUTHORS OR COPYRIGHT HOLDERS BE LIABLE FOR ANY CLAIM, DAMAGES OR OTHERLIA-  #
# BILITY, WHETHER IN AN ACTION OF CONTRACT, TORT OR OTHERWISE, ARISING FROM,  #
# OUT OF OR IN CONNECTION WITH THE SOFTWARE OR THE USE OR OTHER DEALINGS IN   #
# THE SOFTWARE.                                                               #
#                                                                             #
# # # # # # # # # # # # # # # # # # # # # # # # # # # # # # # # # # # # # # # #
